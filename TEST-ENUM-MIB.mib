TEST-ENUM-MIB DEFINITIONS ::= BEGIN

IMPORTS
    MODULE-IDENTITY, OBJECT-TYPE, Integer32, Unsigned32, enterprises,
        IpAddress, NOTIFICATION-TYPE
        FROM SNMPv2-SMI
    MODULE-COMPLIANCE, OBJECT-GROUP, NOTIFICATION-GROUP
        FROM SNMPv2-CONF
    DisplayString, RowStatus
        FROM SNMPv2-TC;

testEnumMIB MODULE-IDENTITY
    LAST-UPDATED "202604030000Z"
    ORGANIZATION "Test Organisation"
    CONTACT-INFO
        "Postal: Test Organisation
                 1 Example Street
                 Anytown, UK
         Email:  mib-admin@example.com"
    DESCRIPTION
        "Test MIB for inline enum handling, RowStatus table creation,
         notifications, composite indexes, simple indexed tables,
         and AUGMENTS processing."
    REVISION     "202604030000Z"
    DESCRIPTION  "Updated the conformance section to align with SMIv2
                  practice; added missing object groups for augmented
                  table columns; corrected DESCRIPTION punctuation;
                  added a named enumeration for eventSeverity; and
                  removed accessible-for-notify objects from OBJECT-GROUP
                  in line with RFC 2580 section 3.1. Those objects are
                  covered via NOTIFICATION-TYPE OBJECTS clauses and the
                  NOTIFICATION-GROUP."
    REVISION     "202604020000Z"
    DESCRIPTION  "Added RowStatus-driven createAndGo/createAndWait semantics
                  to testEnumTable."
    REVISION     "202603300000Z"
    DESCRIPTION  "Added completion and event notification examples for trap
                  testing."
    REVISION     "202602060000Z"
    DESCRIPTION  "Initial version."
    ::= { enterprises 99998 }

testEnumNotifications OBJECT IDENTIFIER ::= { testEnumMIB 0 }
testEnumObjects       OBJECT IDENTIFIER ::= { testEnumMIB 1 }
testEnumConformance   OBJECT IDENTIFIER ::= { testEnumMIB 2 }

-- ============================================================
-- Scalars
-- ============================================================

testScalars OBJECT IDENTIFIER ::= { testEnumObjects 1 }

testColour OBJECT-TYPE
    SYNTAX      INTEGER {
                    red(1),
                    green(2),
                    blue(3),
                    yellow(4)
                }
    MAX-ACCESS  read-only
    STATUS      current
    DESCRIPTION
        "A colour value with no zero value in the enumeration."
    ::= { testScalars 1 }

testPriority OBJECT-TYPE
    SYNTAX      INTEGER {
                    low(10),
                    medium(20),
                    high(30),
                    critical(50)
                }
    MAX-ACCESS  read-only
    STATUS      current
    DESCRIPTION
        "Priority with non-contiguous values starting well above zero."
    ::= { testScalars 2 }

completionSource OBJECT-TYPE
    SYNTAX      DisplayString (SIZE (0..64))
    MAX-ACCESS  accessible-for-notify
    STATUS      current
    DESCRIPTION
        "Source of the completion action (CLI, switch, automation, etc.)."
    ::= { testScalars 3 }

completionCode OBJECT-TYPE
    SYNTAX      Integer32 (0..2147483647)
    MAX-ACCESS  accessible-for-notify
    STATUS      current
    DESCRIPTION
        "Equipment-defined completion code for the finished
         command or action."
    ::= { testScalars 4 }

eventSeverity OBJECT-TYPE
    SYNTAX      INTEGER {
                    clear(0),
                    info(1),
                    minor(2),
                    major(3),
                    critical(4),
                    emergency(5)
                }
    MAX-ACCESS  accessible-for-notify
    STATUS      current
    DESCRIPTION
        "Alarm severity level.  clear(0) indicates the alarm condition
         has been resolved."
    ::= { testScalars 5 }

eventText OBJECT-TYPE
    SYNTAX      DisplayString (SIZE (0..255))
    MAX-ACCESS  accessible-for-notify
    STATUS      current
    DESCRIPTION
        "Human-readable alarm or event text."
    ::= { testScalars 6 }

-- ============================================================
-- Enum Table
-- ============================================================

testEnumTable OBJECT-TYPE
    SYNTAX      SEQUENCE OF TestEnumEntry
    MAX-ACCESS  not-accessible
    STATUS      current
    DESCRIPTION
        "Table for testing inline enum handling."
    ::= { testEnumObjects 2 }

testEnumEntry OBJECT-TYPE
    SYNTAX      TestEnumEntry
    MAX-ACCESS  not-accessible
    STATUS      current
    DESCRIPTION
        "An entry in the test enum table."
    INDEX       { testEnumIndex }
    ::= { testEnumTable 1 }

TestEnumEntry ::= SEQUENCE {
    testEnumIndex       Unsigned32,
    testRowColour       INTEGER,
    testRowPriority     INTEGER,
    testRowStatus       RowStatus
}

testEnumIndex OBJECT-TYPE
    SYNTAX      Unsigned32 (1..4294967295)
    MAX-ACCESS  not-accessible
    STATUS      current
    DESCRIPTION
        "Row index for the test enum table."
    ::= { testEnumEntry 1 }

testRowColour OBJECT-TYPE
    SYNTAX      INTEGER {
                    red(1),
                    green(2),
                    blue(3),
                    yellow(4)
                }
    MAX-ACCESS  read-create
    STATUS      current
    DESCRIPTION
        "A colour column with no zero value in the enumeration."
    ::= { testEnumEntry 2 }

testRowPriority OBJECT-TYPE
    SYNTAX      INTEGER {
                    low(10),
                    medium(20),
                    high(30),
                    critical(50)
                }
    MAX-ACCESS  read-create
    STATUS      current
    DESCRIPTION
        "Priority column with non-contiguous values."
    ::= { testEnumEntry 3 }

testRowStatus OBJECT-TYPE
    SYNTAX      RowStatus
    MAX-ACCESS  read-create
    STATUS      current
    DESCRIPTION
        "Row lifecycle control for testEnumTable.  Managers can create
         rows with createAndGo(4) or createAndWait(5), activate with
         active(1), and remove with destroy(6)."
    ::= { testEnumEntry 4 }

-- ============================================================
-- Endpoint Table
-- ============================================================

endPointTable OBJECT-TYPE
    SYNTAX      SEQUENCE OF EndPointEntry
    MAX-ACCESS  not-accessible
    STATUS      current
    DESCRIPTION
        "Table for endpoint configuration."
    ::= { testEnumObjects 3 }

endPointEntry OBJECT-TYPE
    SYNTAX      EndPointEntry
    MAX-ACCESS  not-accessible
    STATUS      current
    DESCRIPTION
        "An entry in the endpoint table."
    INDEX       { endPointIpAddress, endPointPort }
    ::= { endPointTable 1 }

EndPointEntry ::= SEQUENCE {
    endPointIpAddress   IpAddress,
    endPointPort        Unsigned32,
    endPointName        DisplayString,
    endPointNotes       DisplayString
}

endPointIpAddress OBJECT-TYPE
    SYNTAX      IpAddress
    MAX-ACCESS  not-accessible
    STATUS      current
    DESCRIPTION
        "IP address of the endpoint."
    ::= { endPointEntry 1 }

endPointPort OBJECT-TYPE
    SYNTAX      Unsigned32 (1..65535)
    MAX-ACCESS  not-accessible
    STATUS      current
    DESCRIPTION
        "Port number of the endpoint."
    ::= { endPointEntry 2 }

endPointName OBJECT-TYPE
    SYNTAX      DisplayString (SIZE (0..255))
    MAX-ACCESS  read-write
    STATUS      current
    DESCRIPTION
        "Human-readable name of the endpoint."
    ::= { endPointEntry 3 }

endPointNotes OBJECT-TYPE
    SYNTAX      DisplayString (SIZE (0..1024))
    MAX-ACCESS  read-write
    STATUS      current
    DESCRIPTION
        "Operator notes associated with the endpoint."
    ::= { endPointEntry 4 }

-- ============================================================
-- Multi-Index RowStatus Table
-- ============================================================

testAddrStatusTable OBJECT-TYPE
    SYNTAX      SEQUENCE OF TestAddrStatusEntry
    MAX-ACCESS  not-accessible
    STATUS      current
    DESCRIPTION
        "Table that combines IpAddress and slot indexes with RowStatus
         lifecycle semantics."
    ::= { testEnumObjects 7 }

testAddrStatusEntry OBJECT-TYPE
    SYNTAX      TestAddrStatusEntry
    MAX-ACCESS  not-accessible
    STATUS      current
    DESCRIPTION
        "An entry identified by {address, slot}."
    INDEX       { testAddrStatusAddress, testAddrStatusSlot }
    ::= { testAddrStatusTable 1 }

TestAddrStatusEntry ::= SEQUENCE {
    testAddrStatusAddress  IpAddress,
    testAddrStatusSlot     Unsigned32,
    testAddrStatusColour   INTEGER,
    testAddrStatusPriority INTEGER,
    testAddrStatusRowStatus RowStatus
}

testAddrStatusAddress OBJECT-TYPE
    SYNTAX      IpAddress
    MAX-ACCESS  not-accessible
    STATUS      current
    DESCRIPTION
        "IPv4 address index component for the multi-index RowStatus table."
    ::= { testAddrStatusEntry 1 }

testAddrStatusSlot OBJECT-TYPE
    SYNTAX      Unsigned32 (1..65535)
    MAX-ACCESS  not-accessible
    STATUS      current
    DESCRIPTION
        "Slot index component for the multi-index RowStatus table."
    ::= { testAddrStatusEntry 2 }

testAddrStatusColour OBJECT-TYPE
    SYNTAX      INTEGER {
                    red(1),
                    green(2),
                    blue(3),
                    yellow(4)
                }
    MAX-ACCESS  read-create
    STATUS      current
    DESCRIPTION
        "Colour payload column for the multi-index RowStatus table."
    ::= { testAddrStatusEntry 3 }

testAddrStatusPriority OBJECT-TYPE
    SYNTAX      INTEGER {
                    low(10),
                    medium(20),
                    high(30),
                    critical(50)
                }
    MAX-ACCESS  read-create
    STATUS      current
    DESCRIPTION
        "Priority payload column for the multi-index RowStatus table."
    ::= { testAddrStatusEntry 4 }

testAddrStatusRowStatus OBJECT-TYPE
    SYNTAX      RowStatus
    MAX-ACCESS  read-create
    STATUS      current
    DESCRIPTION
        "Row lifecycle for testAddrStatusTable. Managers can create rows
         with createAndGo(4) or createAndWait(5), activate with active(1),
         and remove with destroy(6)."
    ::= { testAddrStatusEntry 5 }

-- ============================================================
-- Inference Table
-- ============================================================

testInferenceTable OBJECT-TYPE
    SYNTAX      SEQUENCE OF TestInferenceEntry
    MAX-ACCESS  not-accessible
    STATUS      current
    DESCRIPTION
        "Table with a single-column index used for parser and
         inference testing."
    ::= { testEnumObjects 4 }

testInferenceEntry OBJECT-TYPE
    SYNTAX      TestInferenceEntry
    MAX-ACCESS  not-accessible
    STATUS      current
    DESCRIPTION
        "Entry with a simple single-column index for inference testing."
    INDEX       { testInferenceIndex }
    ::= { testInferenceTable 1 }

TestInferenceEntry ::= SEQUENCE {
    testInferenceIndex  Integer32,
    testInferenceValue  Integer32
}

testInferenceIndex OBJECT-TYPE
    SYNTAX      Integer32
    MAX-ACCESS  not-accessible
    STATUS      current
    DESCRIPTION
        "Primary row index column used to identify each
         testInferenceEntry row."
    ::= { testInferenceEntry 1 }

testInferenceValue OBJECT-TYPE
    SYNTAX      Integer32
    MAX-ACCESS  read-only
    STATUS      current
    DESCRIPTION
        "Non-index payload column used for inference and value
         decoding checks."
    ::= { testInferenceEntry 2 }

-- ============================================================
-- Augmented Table Pair
-- ============================================================

testAugBaseTable OBJECT-TYPE
    SYNTAX      SEQUENCE OF TestAugBaseEntry
    MAX-ACCESS  not-accessible
    STATUS      current
    DESCRIPTION
        "Base table used for AUGMENTS testing."
    ::= { testEnumObjects 5 }

testAugBaseEntry OBJECT-TYPE
    SYNTAX      TestAugBaseEntry
    MAX-ACCESS  not-accessible
    STATUS      current
    DESCRIPTION
        "Base row with mixed data types."
    INDEX       { testAugBaseIndex }
    ::= { testAugBaseTable 1 }

TestAugBaseEntry ::= SEQUENCE {
    testAugBaseIndex       Unsigned32,
    testAugBase01Int       Integer32,
    testAugBase02Unsigned  Unsigned32,
    testAugBase03Name      DisplayString,
    testAugBase04Address   IpAddress,
    testAugBase05Payload   OCTET STRING
}

testAugBaseIndex OBJECT-TYPE
    SYNTAX      Unsigned32 (1..4294967295)
    MAX-ACCESS  not-accessible
    STATUS      current
    DESCRIPTION
        "Base table row index."
    ::= { testAugBaseEntry 1 }

testAugBase01Int OBJECT-TYPE
    SYNTAX      Integer32
    MAX-ACCESS  read-only
    STATUS      current
    DESCRIPTION
        "Signed integer base column."
    ::= { testAugBaseEntry 2 }

testAugBase02Unsigned OBJECT-TYPE
    SYNTAX      Unsigned32
    MAX-ACCESS  read-only
    STATUS      current
    DESCRIPTION
        "Unsigned integer base column."
    ::= { testAugBaseEntry 3 }

testAugBase03Name OBJECT-TYPE
    SYNTAX      DisplayString (SIZE (0..64))
    MAX-ACCESS  read-only
    STATUS      current
    DESCRIPTION
        "Display string base column."
    ::= { testAugBaseEntry 4 }

testAugBase04Address OBJECT-TYPE
    SYNTAX      IpAddress
    MAX-ACCESS  read-only
    STATUS      current
    DESCRIPTION
        "IP address base column."
    ::= { testAugBaseEntry 5 }

testAugBase05Payload OBJECT-TYPE
    SYNTAX      OCTET STRING (SIZE (0..64))
    MAX-ACCESS  read-only
    STATUS      current
    DESCRIPTION
        "Octet string base column."
    ::= { testAugBaseEntry 6 }

testAugExtTable OBJECT-TYPE
    SYNTAX      SEQUENCE OF TestAugExtEntry
    MAX-ACCESS  not-accessible
    STATUS      current
    DESCRIPTION
        "Extension table augmenting testAugBaseEntry."
    ::= { testEnumObjects 6 }

testAugExtEntry OBJECT-TYPE
    SYNTAX      TestAugExtEntry
    MAX-ACCESS  not-accessible
    STATUS      current
    DESCRIPTION
        "Augmenting row that extends base table rows."
    AUGMENTS    { testAugBaseEntry }
    ::= { testAugExtTable 1 }

TestAugExtEntry ::= SEQUENCE {
    testAugExt01Status      INTEGER,
    testAugExt02Counter     Integer32,
    testAugExt03Rate        Unsigned32,
    testAugExt04LastChange  Unsigned32,
    testAugExt05Owner       DisplayString,
    testAugExt06Tag         DisplayString,
    testAugExt07Address     IpAddress,
    testAugExt08Payload     OCTET STRING,
    testAugExt09Flag        INTEGER,
    testAugExt10Code        Unsigned32
}

testAugExt01Status OBJECT-TYPE
    SYNTAX      INTEGER {
                    disabled(1),
                    enabled(2),
                    testing(3)
                }
    MAX-ACCESS  read-only
    STATUS      current
    DESCRIPTION
        "Operational status extension column."
    ::= { testAugExtEntry 1 }

testAugExt02Counter OBJECT-TYPE
    SYNTAX      Integer32
    MAX-ACCESS  read-only
    STATUS      current
    DESCRIPTION
        "Signed counter-like extension column."
    ::= { testAugExtEntry 2 }

testAugExt03Rate OBJECT-TYPE
    SYNTAX      Unsigned32
    MAX-ACCESS  read-only
    STATUS      current
    DESCRIPTION
        "Rate extension column."
    ::= { testAugExtEntry 3 }

testAugExt04LastChange OBJECT-TYPE
    SYNTAX      Unsigned32
    MAX-ACCESS  read-only
    STATUS      current
    DESCRIPTION
        "Timestamp-like extension column."
    ::= { testAugExtEntry 4 }

testAugExt05Owner OBJECT-TYPE
    SYNTAX      DisplayString (SIZE (0..64))
    MAX-ACCESS  read-only
    STATUS      current
    DESCRIPTION
        "Owner extension column."
    ::= { testAugExtEntry 5 }

testAugExt06Tag OBJECT-TYPE
    SYNTAX      DisplayString (SIZE (0..64))
    MAX-ACCESS  read-only
    STATUS      current
    DESCRIPTION
        "Tag extension column."
    ::= { testAugExtEntry 6 }

testAugExt07Address OBJECT-TYPE
    SYNTAX      IpAddress
    MAX-ACCESS  read-only
    STATUS      current
    DESCRIPTION
        "Address extension column."
    ::= { testAugExtEntry 7 }

testAugExt08Payload OBJECT-TYPE
    SYNTAX      OCTET STRING (SIZE (0..128))
    MAX-ACCESS  read-only
    STATUS      current
    DESCRIPTION
        "Payload extension column."
    ::= { testAugExtEntry 8 }

testAugExt09Flag OBJECT-TYPE
    SYNTAX      INTEGER {
                    off(0),
                    on(1)
                }
    MAX-ACCESS  read-only
    STATUS      current
    DESCRIPTION
        "Boolean-like flag extension column."
    ::= { testAugExtEntry 9 }

testAugExt10Code OBJECT-TYPE
    SYNTAX      Unsigned32
    MAX-ACCESS  read-only
    STATUS      current
    DESCRIPTION
        "Code extension column."
    ::= { testAugExtEntry 10 }

-- ============================================================
-- Notifications
-- ============================================================

endPointStatusChange NOTIFICATION-TYPE
    OBJECTS {
        endPointIpAddress,
        endPointPort,
        endPointName,
        endPointNotes
    }
    STATUS      current
    DESCRIPTION
        "Notification sent when an endpoint status changes.
         Includes both index columns (IP address and port) plus
         data columns (name and notes)."
    ::= { testEnumNotifications 1 }

completionTrap NOTIFICATION-TYPE
    OBJECTS { completionSource, completionCode }
    STATUS  current
    DESCRIPTION
        "Sent when an internal equipment command or action has
         completed."
    ::= { testEnumNotifications 2 }

eventTrap NOTIFICATION-TYPE
    OBJECTS { eventSeverity, eventText }
    STATUS  current
    DESCRIPTION
        "Sent for equipment events and alarms."
    ::= { testEnumNotifications 3 }

-- ============================================================
-- Conformance
-- ============================================================

testEnumCompliance MODULE-COMPLIANCE
    STATUS      current
    DESCRIPTION
        "Compliance statement for the test enum MIB."
    MODULE
        MANDATORY-GROUPS {
            testEnumScalarGroup,
            testEnumTableGroup,
            testEndPointTableGroup,
            testAddrStatusTableGroup,
            testInferenceTableGroup,
            testAugBaseTableGroup,
            testAugExtTableGroup,
            testEnumNotificationGroup
        }
    ::= { testEnumConformance 1 }

testEnumScalarGroup OBJECT-GROUP
    OBJECTS {
        testColour,
        testPriority
    }
    STATUS      current
    DESCRIPTION
        "Read-only scalar objects."
    ::= { testEnumConformance 2 }

testEnumTableGroup OBJECT-GROUP
    OBJECTS {
        testRowColour,
        testRowPriority,
        testRowStatus
    }
    STATUS      current
    DESCRIPTION
        "Accessible columns of the test enum table."
    ::= { testEnumConformance 3 }

testEndPointTableGroup OBJECT-GROUP
    OBJECTS {
        endPointName,
        endPointNotes
    }
    STATUS      current
    DESCRIPTION
        "Accessible columns of the endpoint table."
    ::= { testEnumConformance 4 }

testInferenceTableGroup OBJECT-GROUP
    OBJECTS {
        testInferenceValue
    }
    STATUS      current
    DESCRIPTION
        "Accessible columns of the inference table."
    ::= { testEnumConformance 5 }

testAddrStatusTableGroup OBJECT-GROUP
    OBJECTS {
        testAddrStatusColour,
        testAddrStatusPriority,
        testAddrStatusRowStatus
    }
    STATUS      current
    DESCRIPTION
        "Accessible columns of the multi-index RowStatus table."
    ::= { testEnumConformance 9 }

testAugBaseTableGroup OBJECT-GROUP
    OBJECTS {
        testAugBase01Int,
        testAugBase02Unsigned,
        testAugBase03Name,
        testAugBase04Address,
        testAugBase05Payload
    }
    STATUS      current
    DESCRIPTION
        "Accessible columns of the augmented base table."
    ::= { testEnumConformance 6 }

testAugExtTableGroup OBJECT-GROUP
    OBJECTS {
        testAugExt01Status,
        testAugExt02Counter,
        testAugExt03Rate,
        testAugExt04LastChange,
        testAugExt05Owner,
        testAugExt06Tag,
        testAugExt07Address,
        testAugExt08Payload,
        testAugExt09Flag,
        testAugExt10Code
    }
    STATUS      current
    DESCRIPTION
        "Accessible columns of the augmented extension table."
    ::= { testEnumConformance 7 }

testEnumNotificationGroup NOTIFICATION-GROUP
    NOTIFICATIONS {
        endPointStatusChange,
        completionTrap,
        eventTrap
    }
    STATUS      current
    DESCRIPTION
        "Notifications defined in this MIB."
    ::= { testEnumConformance 8 }

END
